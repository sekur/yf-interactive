module yf-interactive {
  prefix yfi;

  import yangforge { prefix yf; }

  feature browser {
    description "When enabled, generates web client browser application interface";
    if-feature yf:express;
  }

  augment "/yf:run/yf:input/yf:options" {
    description
      "Additional RPC run parameters";
    
    leaf browser {
      description "enables web client interface";
      type boolean;
      default true;
    }
    
  }
}
